Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
Private Sub AcadDocument_BeginSave(ByVal FileName As String)

End Sub

Attribute VB_Name = "UserForm1"
Attribute VB_Base = "0{E0227BD2-B130-4A48-B19C-2ED3E73A0251}{75AD4254-BDD5-43C0-9542-39802969C8E2}"
Attribute VB_GlobalNameSpace = False
Attribute VB_Creatable = False
Attribute VB_PredeclaredId = True
Attribute VB_Exposed = False
Attribute VB_TemplateDerived = False
Attribute VB_Customizable = False
Private Sub cmdGenerateNodes_Click()
    'On Error GoTo cmdGenerateNodesErr
    Dim obj As AcadObject
    'acdbpoint; acdbpolyline
    For Each obj In ThisDrawing.ModelSpace
        MsgBox obj.ObjectName
    Next obj
    Exit Sub
cmdGenerateNodesErr:
    MsgBox "Error in Sub: " & Err.Description, vbOKOnly + vbCritical
End Sub

Private Sub cmdWriteNodes_Click()
    'On Error GoTo cmdWriteobjsErr
    Dim obj As AcadLine
    Dim path As String
    path = "c:\output.txt"
    Open path For Output As #1
    Dim i As Integer
    i = 0
    For Each obj In ThisDrawing.ModelSpace
        i = i + 2
    Next obj
    Write #1, i
    i = 0
    For Each obj In ThisDrawing.ModelSpace
        i = i + 1
        'MsgBox obj.StartPoint(0)
        Write #1, i, Round(obj.StartPoint(0), 2), Round(obj.StartPoint(1), 2)
        i = i + 1
        Write #1, i, Round(obj.EndPoint(0), 2), Round(obj.EndPoint(1), 2)
    Next obj
'    For Each obj In ThisDrawing.ModelSpace
'        'Write #1, i, Round(obj. , 2), Round(obj.Coordinates(1), 2)
'    Next obj
    Close (1)
    Exit Sub
cmdWriteobjsErr:
    MsgBox "Error in Sub: " & Err.Description, vbOKOnly + vbCritical
    Close (1)
End Sub

Private Sub UserForm_Click()

End Sub
